X509PKIXModule DEFINITIONS ::= BEGIN

-- X.509 (PKIX) SubjectPublicKeyInfo field
-- https://tools.ietf.org/html/rfc5912

SubjectPublicKeyInfo  ::=  SEQUENCE  {
     algorithm         AlgorithmIdentifier,
     subjectPublicKey  BIT STRING
}

AlgorithmIdentifier  ::=  SEQUENCE  {
     algorithm   OBJECT IDENTIFIER,
     parameters  ANY DEFINED BY algorithm OPTIONAL
}

-- RSA PK Algorithm, Parameters, and Keys
-- https://tools.ietf.org/html/rfc3279

pkcs-1 OBJECT IDENTIFIER  ::=  {
    iso(1) member-body(2) us(840) rsadsi(113549) pkcs(1) 1
}

rsaEncryption OBJECT IDENTIFIER  ::=  {  pkcs-1 1  }

-- Elliptic Curves in ANSI X9.62
-- https://tools.ietf.org/html/rfc5480

ansi-X9-62 OBJECT IDENTIFIER  ::=  {
    iso(1) member-body(2) us(840) ansi-X9-62(10045)
}
id-public-key-type OBJECT IDENTIFIER  ::=  {  ansi-X9.62 keyType(2)  }
id-ecPublicKey OBJECT IDENTIFIER  ::=  {  id-publicKeyType 1  }

ECParameters  ::=  CHOICE  {
    namedCurve         OBJECT IDENTIFIER
    -- implicitCurve   NULL
    -- specifiedCurve  SpecifiedECDomain
}

secp192r1 OBJECT IDENTIFIER  ::=  {
    iso(1) member-body(2) us(840) ansi-X9-62(10045) curves(3) prime(1) 1
}

sect163k1 OBJECT IDENTIFIER  ::=  {
    iso(1) identified-organization(3) certicom(132) curve(0) 1
}

sect163r2 OBJECT IDENTIFIER  ::=  {
    iso(1) identified-organization(3) certicom(132) curve(0) 15
}

secp224r1 OBJECT IDENTIFIER  ::=  {
    iso(1) identified-organization(3) certicom(132) curve(0) 33
}

sect233k1 OBJECT IDENTIFIER  ::=  {
    iso(1) identified-organization(3) certicom(132) curve(0) 26
}

sect233r1 OBJECT IDENTIFIER  ::=  {
    iso(1) identified-organization(3) certicom(132) curve(0) 27
}

secp256r1 OBJECT IDENTIFIER  ::=  {
    iso(1) member-body(2) us(840) ansi-X9-62(10045) curves(3) prime(1) 7
}

sect283k1 OBJECT IDENTIFIER  ::=  {
    iso(1) identified-organization(3) certicom(132) curve(0) 16
}

sect283r1 OBJECT IDENTIFIER  ::=  {
    iso(1) identified-organization(3) certicom(132) curve(0) 17
}

secp384r1 OBJECT IDENTIFIER  ::=  {
    iso(1) identified-organization(3) certicom(132) curve(0) 34
}

sect409k1 OBJECT IDENTIFIER  ::=  {
    iso(1) identified-organization(3) certicom(132) curve(0) 36
}

sect409r1 OBJECT IDENTIFIER ::= {
    iso(1) identified-organization(3) certicom(132) curve(0) 37
}

secp521r1 OBJECT IDENTIFIER ::= {
    iso(1) identified-organization(3) certicom(132) curve(0) 35
}

sect571k1 OBJECT IDENTIFIER ::= {
    iso(1) identified-organization(3) certicom(132) curve(0) 38
}

sect571r1 OBJECT IDENTIFIER ::= {
    iso(1) identified-organization(3) certicom(132) curve(0) 39
}

END
